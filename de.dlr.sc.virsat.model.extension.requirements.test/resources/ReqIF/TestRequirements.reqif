# IBM Engineering Requirements Tue Mar 16 13:46:18 UTC 2021

# Specification: TestSpecification
- Artifact Format: Module
- ReqIF.Name: TestSpecification

## 99095: TestRequirement (System Requirement)
- Verification Method: Not Set
- Test Criteria: None
- Accepted: false
- Priority: High
- Requirement Type: Functional
- Verifiability: false
- Artifact Format: Text

## 99096: Mission Requirements (Heading)
- Artifact Format: Text

### 99097: Test Child Requirement (System Requirement)
- Artifact Format: Text
- Verification Method: Not Set
- Test Criteria: None
- Requirement Type: Functional
- Accepted: false
- Verifiability: false

# Specification: Test Hardware Specification
- ReqIF.Name: Test Hardware Specification
- Artifact Format: Module

## 99099: Mission Objectives (Heading)
- Artifact Format: Text

### 99100: Test Hardware Requirement (Hardware Requirement)
- Artifact Format: Text
